FME workspace Spatial Analysis Workspace.fmw

Parameters:
- DestDataset_OGCGEOPACKAGE = $(FME_MF_DIR)Output\ass03_output.gpkg   # GeoPackage File
- DestDataset_OGCGEOPACKAGE_5 = $(FME_MF_DIR)Output\ass03_output.gpkg   # GeoPackage File
- DestDataset_OGCGEOPACKAGE_4 = $(FME_MF_DIR)Output\ass03_output.gpkg   # GeoPackage File
- Xmin = 463162.15165937506   # XminData
- Xmax = 486965.54025851935   # XmaxData
- Ymax = 4974930.476262746   # YmaxData
- Ymin = 4960788.011319084   # YminData

Readers:
- SAFE.ESRI-AGOL.ARCGISFEATURESERVICE_1: SAFE.ESRI-AGOL.ARCGISFEATURESERVICE in EPSG:2961
- SAFE.ESRI-AGOL.ARCGISFEATURESERVICE_2: SAFE.ESRI-AGOL.ARCGISFEATURESERVICE in EPSG:2961
- SAFE.ESRI-AGOL.ARCGISFEATURESERVICE_3: SAFE.ESRI-AGOL.ARCGISFEATURESERVICE in EPSG:2961
- SAFE.ESRI-AGOL.ARCGISFEATURESERVICE_4: SAFE.ESRI-AGOL.ARCGISFEATURESERVICE in 26920

Writers:
- OGCGEOPACKAGE_1: OGCGEOPACKAGE to $(DestDataset_OGCGEOPACKAGE)
- OGCGEOPACKAGE_2: OGCGEOPACKAGE to $(DestDataset_OGCGEOPACKAGE_5)
- OGCGEOPACKAGE_3: OGCGEOPACKAGE to $(DestDataset_OGCGEOPACKAGE_4)

Note: Assignment 03: Workspace B / Name: Luis Maldonado / Date: March 8th, 2026
Sites for First Location (reader SAFE.ESRI-AGOL.ARCGISFEATURESERVICE_4)
    attributes: OBJECTID OID, UniqNum SmallInteger, Description String(50), BUFF_DIST SmallInteger
    -> CoordinateSetter
Note: Brings the Bounding Box Limits from Workspace A
WorkspaceARunner: WorkspaceRunner
    BLOCKING = No
    INPUT_PORT_CONNECTED = CONNECTED
    MAX_TO_BATCH = 1
    OVERWRITE_LOG_FILE = HONOR
    WORKSPACE_FILE = $(FME_MF_DIR_ENCODED)ass03_WorkspaceBoundingBox.fmw
    WORKSPACE_PARAMETERS = Xmin,$(Xmin),Xmax,$(Xmax),Ymax,$(Ymax),Ymin,$(Ymin)
    SUCCEEDED -> Location_Counties_AOAOverlay [AREA]
    SUCCEEDED -> Location_Forest_AOAOverlay [AREA]
    SUCCEEDED -> Location_Soil_AOAOverlay [AREA]
NSCounties_WKID2961 (reader SAFE.ESRI-AGOL.ARCGISFEATURESERVICE_1)
    attributes: OBJECTID OID, COUNTY String(30), Shape__Area Double, Shape__Length Double
    -> Location_Counties_AOAOverlay [AREA]
Counties (writer OGCGEOPACKAGE_1)
    attributes: description text(50), county text(30), area double
NSSoilsPg_WKID2961 (reader SAFE.ESRI-AGOL.ARCGISFEATURESERVICE_2)
    attributes: OBJECTID OID, MAPUNIT String(68), CMP SmallInteger, PERCENT_ SmallInteger, SLOPE Single, STONINESS String(1), SOILTYPE String(9), BONK String(1), PROVINCE String(2), MU_GROUP String(4), SN_GROUP String(6), SLPCLS String(2), DATE_ Date, LU_FLAG String(1), SOILNAME String(24), KIND String(1), WATERTBL String(2), ROOTRESTRI String(1), RESTR_TYPE String(2), DRAINAGE String(2), MDEP1 String(4), MDEP2 String(4), MDEP3 String(4), ORDER_ String(2), S_GROUP String(4), G_GROUP String(3), ORDER3 String(2), S_GROUP3 String(5), G_GROUP3 String(3), PROFILE String(14),
      LAYER_NO String(1), HZN_LIT String(1), HZN_MAS String(3), HZN_SUF String(7), HZN_MOD String(1), UDEPTH SmallInteger, LDEPTH SmallInteger, COFRAG SmallInteger, COFRAG_N SmallInteger, DOMSAND String(2), VFSAND SmallInteger, VFSAND_N SmallInteger, TSAND SmallInteger, TSAND_N SmallInteger, TSILT SmallInteger, TSILT_N SmallInteger, TCLAY SmallInteger, TCLAY_N SmallInteger, ORGCARB Single, ORGCARB_N SmallInteger, PHCA Single, PHCA_N SmallInteger, PH2 Single, PH2_N SmallInteger, BASES SmallInteger, BASES_N SmallInteger, CEC SmallInteger, CEC_N SmallInteger, KSAT Single, KSAT_N SmallInteger,
      KP0 SmallInteger, KP0_N SmallInteger, KP10 SmallInteger, KP10_N SmallInteger, KP33 SmallInteger, KP33_N SmallInteger, KP1500 SmallInteger, KP1500_N SmallInteger, BD Single, BD_N SmallInteger, EC SmallInteger, EC_N SmallInteger, CACO3 SmallInteger, CACO3_N SmallInteger, VONPOST SmallInteger, VONPOST_N SmallInteger, WOOD SmallInteger, WOOD_N SmallInteger, LAYER_KEY String(10), Shape__Area Double, Shape__Length Double
    -> Location_Soil_AOAOverlay [AREA]
Soil (writer OGCGEOPACKAGE_3)
    attributes: description text(50), area double, stoniness text(1), soilname text(24)
NSForest_Pg (reader SAFE.ESRI-AGOL.ARCGISFEATURESERVICE_3)
    attributes: OBJECTID OID, ID_EFOREST String(9), EUNIT SmallInteger, ESTAND Integer, COUNTYLIB String(1), MAPSTAND String(13), WETLND SmallInteger, LNDTYPE SmallInteger, LNDCLASS SmallInteger, FORNON SmallInteger, SPECIES String(16), CRNCL SmallInteger, HEIGHT SmallInteger, ALLHEIGHT String(1), SS_SPECIES String(2), SS_CRNCL SmallInteger, SS_HEIGHT SmallInteger, SITE_SW SmallInteger, SITE_HW SmallInteger, WETCLASS SmallInteger, WC_TYPE String(2), AVDI_SW SmallInteger, AVDI_HW SmallInteger, AVDI SmallInteger, FLDCHK SmallInteger, COVER_TYPE SmallInteger, PHOTOYR SmallInteger, HECTARES Double, SWDBA SmallInteger, HWDBA SmallInteger,
      TOTBA SmallInteger, SWMRVOL SmallInteger, HWMRVOL SmallInteger, TOTMRVOL SmallInteger, SS_SWBA SmallInteger, SS_HWBA SmallInteger, SS_TOTBA SmallInteger, TOTSTDBA SmallInteger, SSSWMRVOL SmallInteger, SSHWMRVOL SmallInteger, SSTOTMRVOL SmallInteger, TOTSTDMRVO SmallInteger, MAPSHEET String(8), STAND Integer, FOR_NON SmallInteger, SP1 String(2), SP1P SmallInteger, SP2 String(2), SP2P SmallInteger, SP3 String(2), SP3P SmallInteger, SP4 String(2), SP4P SmallInteger, Shape__Area Double, Shape__Length Double
    -> Location_Forest_AOAOverlay [AREA]
Forest (writer OGCGEOPACKAGE_2)
    attributes: description text(50), area double, forest_height smallint, forest_species_1 text(2)

Bookmark: First Location (CRS 2961) is Buffered (125m) and geometry repaired
Note: Does not reproject
CoordinateSetter: CoordinateSystemSetter
    COORDSYS = EPSG:2961
    -> FirstLocationBuffered
Note: 125m buffer
FirstLocationBuffered: Bufferer
    ANGLE = 22.5
    CAP_STYLE_LOOKUP = CAP_ARC
    CORNER_STYLE_LOOKUP = JOIN_ARC
    MODE = AREA
    OFFSET = 125
    OFFSET_UNITS = METERS
    PRECISION = APPROX
    CAP_STYLE = Arc
    CORNER_STYLE = Arc
    BUFFERED -> BufferedGeomVal
BufferedGeomVal: GeometryValidator
    ISSUE_ATTR_NAME = _issues
    PRESETS = OGC SFA
    REPAIR = YES
    RULES = OGC_VALID_CHECK OGC_VERSION]V1.2.0]SPATIAL_SUBSET]<Unused>]REQUIRE_SIMPLE]No]LEGACY_OGC]No]FME_CONTROLLER_QUERY_FILE]transformers/dependencies/geometryvalidator9/OGC_VALID_CHECK.fme]FME_CONTROLLER_CHOICE]OGC_VALID_CHECK
    SUMMARY = DETAILED_SUMMARY
    REPAIRED -> WorkspaceARunner

Bookmark: Counties Overlay Analysis
Location_Counties_AOAOverlay: AreaOnAreaOverlayer
    ACCUM_ATTRS = ALL
    CLEANING_TOLERANCE_LOOKUP = AUTO
    CONNECT_Z_MODE_LOOKUP = FIRST_WINS
    DEAGGREGATE_INPUT = Yes
    OVC_ATTR = _overlaps
    ACCUM_ATTRS_NAME = Merge Incoming Attributes
    CLEANING_TOLERANCE = Automatic
    CONNECT_Z_MODE = First Wins
    AREA -> CountiesTest
Note: Tester > 1 to remove Bounding Box
CountiesTest: Tester
    BOOL_OP = OR
    TEST_CLAUSE = TEST @Value(_overlaps) > 1
    TEST_MODE = TEST
    PASSED -> CalcCountyArea
CalcCountyArea: AreaCalculator
    AREA_ATTR = _area
    AREA_TYPE = Plane Area
    MULT = 1
    -> CountiesAttributeManager
Note: Remove unnecesary attributes and convert area to ha
CountiesAttributeManager: AttributeManager
    ATTR_TABLE:
      RENAME_SET_VALUE Description > description (varchar(50))
      REMOVE _issues{}.count (uint32)
      REMOVE _issues{}.issue_found (buffer)
      REMOVE _issues{}.location_sample.x (real64)
      REMOVE _issues{}.location_sample.y (real64)
      REMOVE _issues{}.location_sample.z (real64)
      RENAME_SET_VALUE COUNTY > county (varchar(30))
      REMOVE _overlaps (uint32)
      RENAME_SET_VALUE _area > area (real64) = @Evaluate(@Value(area)/10000)
    -> Counties (writer OGCGEOPACKAGE_1)

Bookmark: Soil Overlay analysis
Location_Soil_AOAOverlay: AreaOnAreaOverlayer
    ACCUM_ATTRS = ALL
    CLEANING_TOLERANCE_LOOKUP = AUTO
    CONNECT_Z_MODE_LOOKUP = FIRST_WINS
    DEAGGREGATE_INPUT = Yes
    OVC_ATTR = _overlaps
    ACCUM_ATTRS_NAME = Merge Incoming Attributes
    CLEANING_TOLERANCE = Automatic
    CONNECT_Z_MODE = First Wins
    AREA -> SoilTest
Note: Tester > 1 to remove Bounding Box
SoilTest: Tester
    BOOL_OP = OR
    TEST_CLAUSE = TEST @Value(_overlaps) > 1
    TEST_MODE = TEST
    PASSED -> CalcSoilArea
CalcSoilArea: AreaCalculator
    AREA_ATTR = _area
    AREA_TYPE = Plane Area
    MULT = 1
    -> SoilAttributeManager
Note: Remove unnecesary attributes, convert area to ha, and fix description returned values
SoilAttributeManager: AttributeManager
    ATTR_TABLE:
      RENAME_SET_VALUE Description > description (varchar(50)) = FME_CONDITIONAL:DEFAULT_VALUE'Dunbrack Mine
        'BOOL_OP;OR;COMPOSITE_TEST;1;TEST @Value(_overlaps) = 1'Goffs Scheelite Project'BOOL_OP;OR;COMPOSITE_TEST;1;TEST @Value(_overlaps) = 2'Meaghers Grant As Prospect
        'FME_NUM_CONDITIONS3___
      REMOVE _issues{}.count (uint32)
      REMOVE _issues{}.issue_found (buffer)
      REMOVE _issues{}.location_sample.x (real64)
      REMOVE _issues{}.location_sample.y (real64)
      REMOVE _issues{}.location_sample.z (real64)
      REMOVE _overlaps (uint32)
      RENAME_SET_VALUE _area > area (real64) = @Evaluate(@Value(area)/10000)
      RENAME_SET_VALUE STONINESS (varchar(1))
      RENAME_SET_VALUE SOILNAME (varchar(24))
    -> Soil (writer OGCGEOPACKAGE_3)

Bookmark: Forest Overlay Analysis
Location_Forest_AOAOverlay: AreaOnAreaOverlayer
    ACCUM_ATTRS = ALL
    CLEANING_TOLERANCE_LOOKUP = AUTO
    CONNECT_Z_MODE_LOOKUP = FIRST_WINS
    DEAGGREGATE_INPUT = Yes
    OVC_ATTR = _overlaps
    ACCUM_ATTRS_NAME = Merge Incoming Attributes
    CLEANING_TOLERANCE = Automatic
    CONNECT_Z_MODE = First Wins
    AREA -> ForestTest
Note: Tester > 1 to remove Bounding Box
ForestTest: Tester
    BOOL_OP = OR
    TEST_CLAUSE = TEST @Value(_overlaps) > 1
    TEST_MODE = TEST
    PASSED -> CalcForestArea
CalcForestArea: AreaCalculator
    AREA_ATTR = _area
    AREA_TYPE = Plane Area
    MULT = 1
    -> ForestAttributeManager
Note: Remove unnecesary attributes and convert area to ha
ForestAttributeManager: AttributeManager
    ATTR_TABLE:
      RENAME_SET_VALUE Description > description (varchar(50))
      REMOVE _issues{}.count (uint32)
      REMOVE _issues{}.issue_found (buffer)
      REMOVE _issues{}.location_sample.x (real64)
      REMOVE _issues{}.location_sample.y (real64)
      REMOVE _issues{}.location_sample.z (real64)
      REMOVE _overlaps (uint32)
      RENAME_SET_VALUE _area > area (real64) = @Evaluate(@Value(area)/10000)
      RENAME_SET_VALUE HEIGHT > forest_height (int16)
      RENAME_SET_VALUE SP1 > forest_species_1 (varchar(2))
    -> Forest (writer OGCGEOPACKAGE_2)
