FME workspace Data Extraction and Classification Workspace.fmw

Parameters:
- SourceDataset_SHAPEFILE = $(FME_MF_DIR)Transit_Bus_Routes_170400149892654411 (1)\Transit_Bus_Routes.shp   # Source Esri Shapefile(s)
- SourceDataset_CSV2 = $(FME_MF_DIR)Transit_Automated_Passenger_Counts.csv   # Source CSV (Comma Separated Value) File(s)
- DestDataset_GEOJSON = $(FME_MF_DIR)DeliverableLayer\RouteJan23_1pm_Classified.json   # Destination GeoJSON File

Readers:
- SHAPEFILE_1: SHAPEFILE from $(SourceDataset_SHAPEFILE)
- CSV2_1: CSV2 from $(SourceDataset_CSV2)

Writers:
- GEOJSON_1: GEOJSON to $(DestDataset_GEOJSON)

Note: Assignment 02 / Name: Luis Maldonado / Date: February 15th, 2026
Note: Tester is used to Filter both Route_date and Route_hour at the same time
Tester
    BOOL_OP = COMPOSITE
    COMPOSITE_TEST = 1 AND 2
    TEST_CLAUSE:
      TEST @Value(Route_Date) = 1/23/2026 10:00:00 AM
      TEST @Value(Route_Hour) = 13
    TEST_MODE = TEST
    PASSED -> FeatureJoiner [RIGHT]
Note: Join every CSV route number with its respective geometry
FeatureJoiner
    ATTR_CONFLICT_RES = USE_LEFT
    GEOMETRY_HANDLING = USE_LEFT
    JOIN_KEYS = ROUTE_FULL Route_Number AUTO
    JOIN_MODE = Inner
    JOINED -> Classifier
Note: Removes unnecesary fields, create ridership_classification as a new field categorizing records, and convert datetime forat
AttributeManager
    ATTR_TABLE:
      RENAME_SET_VALUE ROUTE_FULL > Route_Identifier (varchar(5))
      RENAME_SET_VALUE TITLE > Route_Title (varchar(50))
      REMOVE Route_Number (varchar(4))
      REMOVE Ridership_Total (uint32)
      SET_TO Route_Date (varchar(21)) = @DateTimeFormat(@DateTimeParse(@Value(Route_Date),%m/%d/%Y %H:%M),%m/%d/%Y %I:%M:%S %p)
      SET_TO Ridership_Classification (varchar(200)) = FME_CONDITIONAL:DEFAULT_VALUE'High'BOOL_OP;OR;COMPOSITE_TEST;1;TEST @Value(_class) = 0'Low'BOOL_OP;OR;COMPOSITE_TEST;1;TEST @Value(_class) = 1'Medium'FME_NUM_CONDITIONS3___
    -> RouteJan23_1pm_Classified (writer GEOJSON_1)
Note: Saves the output as a GeoJSON file
RouteJan23_1pm_Classified (writer GEOJSON_1)
    attributes: Route_Identifier string, Route_Title string, Route_Hour float, Route_Date string, Ridership_Classification string

Bookmark: Original dataset with unnecessary fields removed.
Transit_Bus_Routes (reader SHAPEFILE_1)
    attributes: GLOBALID varchar(38), ROUTE_NUM long, CLASS varchar(20), TITLE varchar(50), SOURCE varchar(12), SACC varchar(2), SDATE date, DATE_ACT date, DATE_REV date, WEEKDAY varchar(1), PEAK varchar(1), WEEKEND varchar(1), ROUTE_ALPA varchar(2), ROUTE_FULL varchar(5)
    -> FeatureJoiner [LEFT]
CSV (reader CSV2_1)
    attributes: OBJECTID uint32, Route_Number varchar(4), Route_Name varchar(34), Ridership_Total uint32, Route_Hour real32, Route_Hour_Description varchar(18), Route_Date varchar(21)
    -> Tester

Bookmark: Classify the dataset based on total ridership, then sort it in ascending order
Classifier
    CLASS_ATTR = _class
    INPUT_VALUE = @Value(Ridership_Total)
    METHOD = NATURAL
    NUM_CLASSES = 3
    CLASSIFIED -> Sorter
Sorter
    SORT_PARM = _class NUMERIC ASCENDING NON_VALUES_AFTER_VALUES
    SORTED -> AttributeManager
